(defun c:skaluj_xy(/ temp_selection pkt skalax skalay)
  (defun *error* (errorlevel)
    (princ "\n MadziCAD error: Funkcja przerwana. ")
  )
  (graphscr)
  (princ "\n Wybierz obiekty do przeskalowania: ")
  (setq temp_selection (ssget))
  (setq pkt (getpoint "\n Wska¿ punkt bazowy: "))
  (setq skalax (getreal "\n Podaj skalê X: "))
  (setq skalay (getreal "\n Podaj skalê Y: "))
  (generuj_losowa_nazwe "temp_block")
  (command "_block" losowa_nazwa pkt temp_selection "")
  (command "_insert" losowa_nazwa pkt skalaX skalaY 0)
  (command "_explode" (entlast))
  (command "_purge" "o" losowa_nazwa "n")
(princ)
)
