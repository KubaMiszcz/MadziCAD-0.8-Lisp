(defun c:convert_to_uppercase(/ temp_selection n sslist temp_entlist bazatxt wysokosc tresc)
  (defun *error* (errorlevel)
    (princ "\n MadziCAD error: Funkcja przerwana. ")
  )
  (graphscr)
  (princ "\n Wskaż tekst lub teksty do zamiany z małych liter na duże: ")
  (setq temp_selection (ssget))
  (selection_to_list temp_selection)
  (setq n 0)
  (foreach item sslist 
    (progn 
      (setq temp_entlist (entget item))
      (if (or (= (cdr (assoc 0 temp_entlist)) "TEXT") (= (cdr (assoc 0 temp_entlist)) "MTEXT"))
        (progn
          (setq bazatxt (cdr (assoc 10 temp_entlist)))
          (setq wysokosc (cdr (assoc 40 temp_entlist)))
          (setq tresc (cdr (assoc 1 temp_entlist)))	
          (command "_mtext" bazatxt "w" "dl" "k" wysokosc bazatxt (strcase tresc) "")
          (command "_matchprop" (nth n sslist) (entlast) "")
          (command "_erase" item "")
          (setq n (1+ n))
        )
      )
    )
  )
  (princ (strcat " " (rtos n)  " obiekty tekstowe przekonwertowano na duże litery. "))
  (princ)
)
