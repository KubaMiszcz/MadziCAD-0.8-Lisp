(defun C:szybki_blok(/ temp_selection block_temp base_pt)
  (defun *error* (errorlevel)
    (princ "\n MadziCAD error: Funkcja przerwana. ")
  )
  (graphscr)
  (princ "\n Wska¿ obiekty z których utworzyæ blok: ")
  (setq temp_selection (ssget))
  (generuj_losowa_nazwe "block_temp_")
  (setq block_temp losowa_nazwa)
  (setq base_pt (cdr(assoc 10(entget (ssname temp_selection 0)))))
  (command "_block" block_temp base_pt temp_selection "")
  (command "_insert" block_temp base_pt 1 1 0)
  (princ (strcat "\n Utworzono blok o nazwie: " block_temp ". "))
  (princ )
)
