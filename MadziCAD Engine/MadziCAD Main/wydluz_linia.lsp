(defun c:wydluz_linia(/ layerprev)
  (defun *error* (errorlevel)
    (entdel (entlast))
    (setvar "clayer" layerprev)
    (princ "\n MadziCAD error: Funkcja przerwana. ")
  )
  (graphscr)
  (setq layerprev (getvar "clayer"))
  (setvar "clayer" "0")
  (princ "\n Narysuj polilinie do ktorej wydłużyć obiekty lub z [SHIFT] uciąć: ")
  (command "_pline" (getpoint))
  (while (= (logand (getvar "cmdactive") 1) 1)
    (command pause)
  )

  (command "_extend" (entlast) ""
    (while (= (logand (getvar "cmdactive") 1) 1)
      (command pause)
    )
  )  
  (entdel (entlast))
  (setvar "clayer" layerprev)
  (princ)
)
