(defun c:ukryj_warstwe_obiektu(/ layer)  				
  (defun *error* (errorlevel)
    (princ "\n MadziCAD error: Funkcja przerwana ")
  )
  (graphscr)
  (princ "\n Wska¿ obiekt na warstwie do ukrycia: ")
  (setq layer (cdr (assoc 8 (entget ( car (entsel))))))
  (if (= layer (getvar "clayer"))
    (command "_Layer" "r" layer "t" "")
    (command "_Layer" "r" layer "")
  )
  (princ)
)
