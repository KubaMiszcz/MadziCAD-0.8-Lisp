(defun c:ukryj_odkryj_obiekty(/ temp_selection block_hh)
  (defun *error* (errorlevel)
    (princ "\n MadziCAD error: Funkcja przerwana ")
  )
  (if 
    (= flaga_ukryj_odkryj nil)
;***nie bylo wczesniej wykonane
    (progn					
      (princ "\n Wybierz obiekty do ukrycia: ")
      (setq temp_selection (ssget))
      (generuj_losowa_nazwe "block_hh")
      (setq block_hh losowa_nazwa)
      (command "_ucs" "g")
      (command "_block" block_hh '(0 0) temp_selection "")
      (command "_ucs" "p")
      (princ (strcat "\n Ukryto " (rtos (sslength temp_selection)) " wybranych obiektów. "))
      (setq flaga_ukryj_odkryj 1)
    )
;***bylo wczesniej wykonane  
    (progn
    (command "_ucs" "g")
    (command "_insert" block_hh '(0 0) 1 1 0)
    (command "_ucs" "p")
    (command "_explode" (entlast))
    (command "_purge" "o" block_hh "n")
    (setq flaga_ukryj_odkryj nil)
    (princ "\n Przywrócono ukryte obiekty. ")
    )
  )
  (princ)
)
