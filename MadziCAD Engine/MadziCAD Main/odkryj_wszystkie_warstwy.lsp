(defun c:odkryj_wszystkie_warstwy() 
  (defun *error* (errorlevel)
    (princ "\n MadziCAD error: Funkcja przerwana. ")
  )
  (graphscr)
  (command "_Layer" "d" "*" "")
  (princ "\n Odkryto wszystkie warstwy. ")
  (princ)
)
