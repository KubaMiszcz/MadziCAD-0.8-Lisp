(defun c:LO()
  (graphscr)
  (setq layerprev (getvar "clayer"))			;zapamietuje biezaca warstwe
  (command "_layer" "u" warwym "")			;ustala akt warstwe na 'wymiary'
  (setvar "dimasz" (* (getvar "dimasz") 2))		;a to bo strzalka jest za mala
  (command "_qleader" 
    (getpoint "\nWskaż pierwszy punkt:")
    (getpoint "\nWskaż drugi punkt:")
    ""
    ""
  )
  (setvar "dimasz" (/ (getvar "dimasz") 2))		;przywraca poprzedni rozmiar strzałki
  (command "_layer" "u" layerprev "")			;zmienia na poprz warstwe
  (princ)
)
