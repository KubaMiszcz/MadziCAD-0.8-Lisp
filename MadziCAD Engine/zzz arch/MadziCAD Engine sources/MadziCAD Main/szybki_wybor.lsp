(defun szybki_wybor_internal(mode / osmodeprev orthoprev temp_selection)
  (defun *error* (errorlevel)
    (setvar "osmode" osmodeprev)  
    (setvar "orthomode" orthoprev) 
    (princ "\n MadziCAD error: Funkcja przerwana. ")
  )
  (graphscr)
  (setq osmodeprev (getvar "osmode"))				;zapamietuje stale tryby lokalizacji
  (setq orthoprev (getvar "orthomode"))				;zapamietuje status orto
  (setvar "osmode" 0)  
  (setvar "orthomode" 0)  
  ;(command "_select" "_single" mode pause)
  (command "_select" "_single" mode pause)
  (sssetfirst nil (ssget "_P"))
  (princ (strcat "\n Utworzono tymczasowy zbiór wskazań z " (rtos(sslength (ssget "_P"))) " obiektów. "))
  (setvar "osmode" osmodeprev)  
  (setvar "orthomode" orthoprev)
  (princ)

)
(defun c:szybki_wybor_krawedz()
  (graphscr)
  (princ "\n Narysuj krawędź przecinającą wybierane obiekty: ")
  (szybki_wybor_internal "_fence")
)
(defun c:szybki_wybor_zamkniety_wielobok()
  (graphscr)
  (princ "\n Narysuj wielobok ZAWIERAJĄCY wybierane obiekty: ")
  (szybki_wybor_internal "_wpolygon")
)
(defun c:szybki_wybor_otwarty_wielobok()
  (graphscr)
  (princ "\n Narysuj wielobok DOTYKAJĄCY wybieranych obiektów: ")
  (szybki_wybor_internal "_cpolygon")
)
(defun c:szybki_wybor_poprzedni()
  (graphscr)
  ;(command "_select" "p" "")
  (sssetfirst nil (ssget "_P"))
  (princ (strcat "\n Utworzono tymczasowy zbiór wskazań z " (rtos(sslength (ssget "_P"))) " poprzednio wybranych obiektów. "))
  (princ)
)
(defun c:szybki_wybor_ostatnio_utworzone()
  (graphscr)
  ;(command "_select" "s" "")
  (sssetfirst nil (ssget "_L"))
  (princ (strcat "\n Utworzono tymczasowy zbiór wskazań z " (rtos(sslength (ssget "_P"))) " ostatnio utworzonych obiektów. "))
  (princ)
)
