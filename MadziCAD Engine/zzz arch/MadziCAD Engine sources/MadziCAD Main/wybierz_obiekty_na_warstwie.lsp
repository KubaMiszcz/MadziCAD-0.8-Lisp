(defun c:wybierz_obiekty_na_warstwie(/ temp_selection sslist filtered_selection layer)
  (defun *error* (errorlevel)
    (princ "\n MadziCAD error: Funkcja przerwana. ")
  )
  (graphscr)
  (princ "\n Wska¿ obiekt na warstwie: ")
  (setq temp_selection (ssget "_:S"))
  (setq layer (cdr (assoc 8 (entget (ssname temp_selection 0)))))
  (princ "\n Zaznacz obszar do przefiltrowania: ")
  (setq temp_selection (ssget))
  (selection_to_list temp_selection)
  (setq filtered_selection (ssadd)) 
  (foreach item sslist
    (setq object_layer (cdr (assoc 8 (entget item))))
    (if 
      (= object_layer layer)
      (ssadd item filtered_selection)
    )
  )
  (sssetfirst nil filtered_selection)
  (princ (strcat "\n Zaznaczono " (itoa (sslength filtered_selection)) " obiektów na warstwie \"" layer "\". "))
  (princ)
)
