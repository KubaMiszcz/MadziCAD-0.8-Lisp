(princ "\n  Funkcję: <MadziCAD Main> załadowano pomyślnie. ") 
(princ "\n  Funkcję: <MadziCAD Mosty Zelbet> załadowano pomyślnie. ")
(princ "\n  Funkcję: <Funkcje Pomocnicze> załadowano pomyślnie. ")
(if (= (open (strcat path "\\support\\MadziCAD_splash_screen.exe") "r") nil)
  (alert "\n Brak pliku MadziCADa.\t")
)
(startapp (strcat path "\\support\\MadziCAD_splash_screen.exe"))
(princ "\n\n © MadziCAD... All OK. ")
