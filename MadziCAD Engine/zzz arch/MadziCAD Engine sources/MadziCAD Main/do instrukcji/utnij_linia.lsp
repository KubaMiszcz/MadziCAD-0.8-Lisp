(defun c:utnij_linia(/ layerprev osmodeprev coords trim_edge pkt entlist vertlist n pkt1 pkt2)
  (defun *error* (errorlevel)
    (setvar "clayer" layerprev)
    (setvar "osmode" osmodeprev)
    (princ "\n MadziCAD error: Funkcja przerwana. ")
  )

  (graphscr)
  (setq layerprev (getvar "clayer"))
  (setq osmodeprev (getvar "osmode"))
  (setq coords nil)
  
  (setvar "clayer" "0")  
  (princ "\n Narysuj polilinie ucinającą: ")
  (command "_pline" (getpoint))
  (while (= (logand (getvar "cmdactive") 1) 1)
    (defun *error* (errorlevel)
      (setvar "clayer" layerprev)
      (entdel(entlast))
      (princ "\n MadziCAD error: Funkcja przerwana. ")
    )
    (command pause)
  )

  (setq trim_edge (entlast))

  (setvar "osmode" 0)
  (setq pkt (getpoint "\n Wskaż od ktorej strony ucinać obiekty: "))
  (command "_offset" 0.01 (entlast) pkt "")

  ;lista wierzcholkow polilinii
  (setq entlist (entget (entlast)))
  (setq vertlist (member (assoc 10 entlist) entlist))
  (repeat (cdr (assoc 90 entlist))
    (setq coords (cons (cdar vertlist) coords) vertlist (cddddr vertlist))
  )
  (entdel (entlast))

  ;ucinanie n-1 razy
  (setq n (- (length coords) 1))
  (repeat n
    (setq pkt1 (trans (nth n coords) 0 1))
    (setq pkt2 (trans (nth (- n 1) coords) 0 1))
    (command "_trim" trim_edge "" "_fence" pkt1 pkt2 "" "")  ;dla pewnosci 6 razy:]
    (command "_trim" trim_edge "" "_fence" pkt1 pkt2 "" "")
    (command "_trim" trim_edge "" "_fence" pkt1 pkt2 "" "")
    (command "_trim" trim_edge "" "_fence" pkt1 pkt2 "" "")
    (command "_trim" trim_edge "" "_fence" pkt1 pkt2 "" "")
    (command "_trim" trim_edge "" "_fence" pkt1 pkt2 "" "")
    (setq n (- n 1))
  )
  (setvar "osmode" osmodeprev)
  (setvar "clayer" layerprev)
  (command "_erase" trim_edge "")
  (princ)
)
