(defun c:otworz_wszystkie_warstwy()
  (defun *error* (errorlevel)
    (princ "\n MadziCAD error: Funkcja przerwana. ")
  )
  (graphscr)
  (command "_Layer" "_unlock" "*" "")
  (princ "\n Otwarto wszystkie warstwy. ")
  (setq layerproplistZOW nil)
  (princ)
)
