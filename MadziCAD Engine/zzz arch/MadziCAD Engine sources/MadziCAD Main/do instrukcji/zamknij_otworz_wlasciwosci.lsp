(defun c:zamknij_otworz_wlasciwosci()
  (defun *error* (errorlevel)
    (princ "\n MadziCAD error: Funkcja przerwana. ")
  )
  (if 
    (= (getvar "opmstate") 0) 
    (progn
      (command "_properties")
      (princ "\n Otwarto okno właściwości. ")
    )
    (progn
      (command "_propertiesclose")
      (princ "\n Zamknięto okno właściwości. ")
    )
  )
  (princ)
)
