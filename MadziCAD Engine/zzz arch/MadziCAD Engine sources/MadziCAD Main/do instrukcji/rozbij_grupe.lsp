(defun c:rozbij_grupe () ; / temp_selection a b c d e f g groupname)
  (defun *error* (errorlevel)
    (princ "\n MadziCAD error: Funkcja przerwana. ")
  )
  (graphscr)
  (princ "\n Wska¿ obiekt w grupie lub bloku do rozbicia: ")
  (setq temp_selection (ssget "_:S"))
  (if 
    (= (cdr (assoc 0 (entget (cdr (assoc 330 (entget (ssname temp_selection 0))))))) "GROUP")
    (progn
      (setq a (entget (ssname temp_selection 0)))
      (setq b (cdr (assoc 330 a)))  
      (setq c (entget b))
      (setq d (cdr (assoc 330 c)))
      (setq e (entget d))
      (setq f (cdr (assoc 330 e)))
      (setq g (entget f))
      (setq groupname (cdr (assoc 3 (reverse g))))  ; nazwa grupy
      ;(command "_group" "r" groupname)  
      (princ(strcat "Grupa " groupname " zosta³a rozbita"))
    )
    (command "_explode" temp_selection)
  )
  (princ)
)
