(defun c:txt_na_mtxt(/ temp_selection n temp_entlist bazatxt wysokosc tresc)
  (defun *error* (errorlevel)
    (princ "\n MadziCAD error: Funkcja przerwana. ")
  )
  (graphscr)
  (princ "\n Wskaż tekst lub teksty jednowierszowe do zamiany na wielowierszowe: ")
  (setq temp_selection (ssget '((0 . "TEXT"))))
  (selection_to_list temp_selection)
  (foreach item sslist
    (progn
      (setq temp_entlist (entget item))
      (setq bazatxt (cdr (assoc 10 temp_entlist)))
      (setq bazatxt (trans bazatxt 0 1))
      (setq wysokosc (cdr (assoc 40 temp_entlist)))
      (setq tresc (cdr (assoc 1 temp_entlist)))	
      (command "_mtext" bazatxt "_justify" "_bl" "_height" wysokosc bazatxt tresc "")
      (command "_matchprop" item (entlast) "")
      (command "_erase" item "")
    )
  )
  (princ (strcat " " (rtos (length sslist))  " tekstów jednowierszowych przekształcono na wielowierszowe. "))
  (princ)
)
