(defun widok(mode/)
  (command "_view" "w" mode)
  ;(command "_regen")
  (princ)
)
(defun c:`1()
  (setq mode "1")
  (widok mode)
)
(defun c:`2()
  (setq mode "1")
  (widok mode)
)
(defun c:`3()
  (setq mode "1")
  (widok mode)
)
