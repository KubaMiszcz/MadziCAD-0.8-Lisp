(defun c:przenies_obiekty_na_warstwe (/ pri_obj pri_layer temp_selection)
  (defun *error* (errorlevel)
    (princ "\n MadziCAD error: Funkcja przerwana. ")
  )
  (graphscr)
  (princ
    "\n Wskaż obiekt na warstwie na którą przenieść obiekty: "
  )
  (setq pri_obj (ssget "_:S"))
  (setq pri_layer (cdr (assoc 8 (entget (ssname pri_obj 0)))))
  (princ
    "\n Wskaż obiekt lub obiekty do przeniesienia na inną warstwę: "
  )
  (setq temp_selection (ssget))
  (command "_chprop" temp_selection "" "_layer" pri_layer "")
  (princ (strcat "\n "
		 (itoa (sslength temp_selection))
		 " obiektów przeniesiono na warstwę "
		 pri_layer
		 ". "
	 )
  )
  (princ)
)
