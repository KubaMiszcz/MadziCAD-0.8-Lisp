(defun c:linia_odniesienia(/ layerprev osmodeprev dimclrtprev orthoprev dimaszprev ostatni_tekst new_text entlist)
  (defun *error* (errorlevel)
    (setvar "osmode" osmodeprev)
    (setvar "orthomode" orthoprev)
    (setvar "dimclrt" dimclrtprev)			;kolor tekstu linii odniesienia
    (setvar "clayer" layerprev)			;zmienia na poprz warstwe
    (princ "\n MadziCAD error: Funkcja przerwana. ")
  )
  (graphscr)
  (setq layerprev (getvar "clayer"))			;zapamietuje biezaca warstwe
  (setq osmodeprev (getvar "osmode"))
  (setq dimclrtprev (getvar "dimclrt"))			;kolor tekstu w stylu wymiarowania
  (setq orthoprev (getvar "orthomode"))
  (setq dimaszprev (getvar "dimasz"))
  (if (/= (tblsearch "layer" warwym) nil)
    (setvar "clayer" warwym)          			;ustala akt warstwe na 'wymiary'
  )
  (setvar "dimclrt" kolor_tekstu_linii_odniesienia)	;kolor tekstu linii odniesienia
  (command "_qleader" 
    (getpoint "\n Wska¿ pierwszy punkt: ")
    (progn 
      (setvar "osmode" 0)
      (setvar "orthomode" 0)
      (princ "\n Wska¿ drugi punkt: ") 
      pause
    )
    ""
    ""
    ""
  )
  
  (setq ostatni_tekst (ssget "_L"))
  
  
;zamiana tekstu na duze litery jesli tak usatawione w pliku ustawienia
  (if (= all_uppercase 1)
    (progn
      (setq entlist (entget (ssname ostatni_tekst 0)))
      (setq new_text (strcase (cdr (assoc 1 entlist))))
      (setq entlist     ;zmiana na duze litery
        (subst 
          (cons 1 new_text) 
          (assoc 1 entlist) 
          entlist
        )
      )
      (entmod entlist)
    )
  )
   
  ;;;;; dodawanie maski 
  (if (= automatyczne_dodawanie_maski_tla_do_tekstow 1)
    (progn
      (setq entlist (entget (ssname ostatni_tekst 0)))
      (setq entlist   
         (append
           entlist
           (list (cons 90 3))       ;dodanie maski 
           (list (cons 63 256))     ;ustawienie maski jak tlo rysuku
           (list (cons 45 rozmiar_maski_w_tekstach))     ;ustawienie rozmiaru maski 1.1        
         )
      )
      (entmod entlist)
    )
  )

  ;;poprawianie podkreslenia
  ;(generuj_losowa_nazwe "linia_odniesienia_")
  ;(command "_group" "_c" losowa_nazwa "" pkt1 (entlast) "")
  
  (setvar "osmode" osmodeprev)
  (setvar "orthomode" orthoprev)
  (setvar "dimclrt" dimclrtprev)      ;kolor tekstu linii odniesienia
  (setvar "clayer" layerprev)         ;zmienia na poprz warstwe
  (princ)
)
