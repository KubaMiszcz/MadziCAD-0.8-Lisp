(defun c:skala_rysowania()
  (defun *error* (errorlevel)
    (princ "\n MadziCAD error: Funkcja przerwana. ")
  )
  (graphscr)
  (princ (strcat "\n Podaj now¹ skalê rysowania <" (rtos (getvar "dimscale")) ">: "))
  (setvar "dimscale" (getint))
  (princ)
)
