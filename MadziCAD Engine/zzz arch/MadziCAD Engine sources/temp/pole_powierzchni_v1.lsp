(defun pole_obwiedni()
  (command "_boundary" "z" "w" "n" "" "t" "r" "" (getpoint "\nWskaż punkt w środku pola powierzchni:") "")
  (command "_area" "o" (ssget "_L"))
  (setq pole_obw (/ (getvar 'area) 1000000))
  (command "_erase" (ssget "_L") "")
  (setq pole_pow_poprz pole_pow)
  (setq pole_pow (+ pole_pow pole_obw))
  (alert (strcat "Całkowite Pole powierzchni: " (rtos pole_pow_poprz 2 2) "+" (rtos pole_obw 2 2) "=" (rtos pole_pow 2 2) " m2"))
  (princ)
)

(defun c:pole_powierzchni()
  (setq pole_pow 0)
  (pole_sumowanie)
  (pole_sumowanie)
  (pole_sumowanie)
  (pole_sumowanie)
  (pole_sumowanie)
  (pole_sumowanie)
  (pole_sumowanie)
  (pole_sumowanie)
  (pole_sumowanie)
  (pole_sumowanie)
  (pole_sumowanie)
  (pole_sumowanie)
  (pole_sumowanie)
)
