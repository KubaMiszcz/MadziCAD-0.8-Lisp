(defun c:za(/ ksztalt_preta filletrad filletradprev thickness)
  (defun *error* (errorlevel)
    (setq filletradprev (getvar "filletrad"))
    (princ "\n MadziCAD error: Funkcja przerwana. ")
  )
  (graphscr)
  (princ "wskaz polilnie:")
  (setq ksztalt_preta (ssget "_:S"))
  (setq thickness (cdr (assoc 40 (entget (ssname ksztalt_preta 0)))))
  (setq filletradprev (getvar "filletrad"))
  (setvar "FILLETRAD" (* 0.5 5 thickness)) 
  (command "_fillet" "_polyline" ksztalt_preta)
  (setvar "filletrad" filletradprev)
  (princ)
)

(defun c:zaa(/ ksztalt_preta)
  (defun *error* (errorlevel)
    (princ "\n MadziCAD error: Funkcja przerwana. ")
  )
  (graphscr)
  (princ "wskaz polilnie:")
  (setq ksztalt_preta (ssget "_:S"))
  (setvar "FILLETRAD" 0)
  (command "_fillet" "_polyline" ksztalt_preta)  
  (princ)
)
